module example-types {
  namespace "urn:example:types";
  prefix ty;

  container types {
    leaf num-or-name {
      type union {
        type uint8;
        type string;
      }
    }
    leaf flags {
      type bits {
        bit up;
        bit down;
      }
    }
    leaf ratio {
      type decimal64 {
        fraction-digits 2;
        range "0..100";
      }
    }
    leaf marker {
      type empty;
    }
    leaf blob {
      type binary;
    }
    leaf target {
      type instance-identifier;
    }
  }
}
