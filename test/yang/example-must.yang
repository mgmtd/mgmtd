module example-must {
  namespace "urn:example:must";
  prefix m;

  list interface {
    key "name";
    leaf name {
      type string;
    }
    leaf enabled {
      type boolean;
    }
    leaf outgoing-interface {
      type string;
      must "/interface[name=current()]/enabled = 'true'" {
        error-message "Outgoing interface must be enabled";
      }
    }
  }

  container box {
    must "1 = 1";
    leaf flag {
      type boolean;
    }
    leaf extra {
      type string;
      when "../flag = 'true'";
    }
    leaf gated {
      type string;
      must "../flag = 'true'" {
        error-message "flag must be true";
      }
    }
  }
}
